[DOCUMENT]
TITLE: 00 Stakeholder needs

[GRAMMAR]
IMPORT_FROM_FILE: bench.sgra

[TEXT]
STATEMENT: >>>
Level 0 of the requirement hierarchy: what drivers, other road users, service engineers and developers need from the vehicle, in their own language. Every system requirement traces to at least one stakeholder need. IDs: STK-NNN.
<<<

[REQUIREMENT]
UID: STK-001
STATUS: Draft
KIND: Functional
VERIFICATION: Demonstration
TITLE: Signal intention to other road users
STATEMENT: >>>
The driver can signal an intended change of direction, and warn other road users of a hazard, in a way they recognise immediately.
<<<

[REQUIREMENT]
UID: STK-002
STATUS: Draft
KIND: Functional
VERIFICATION: Demonstration
TITLE: See and be seen
STATEMENT: >>>
The driver can switch on the vehicle's low beam so that the vehicle is visible to others.
<<<

[REQUIREMENT]
UID: STK-003
STATUS: Draft
KIND: Non-functional
VERIFICATION: Demonstration
RELEVANCE: Safety
TITLE: Predictable behaviour when something fails
STATEMENT: >>>
When a component or its communication fails, the vehicle stays in a predictable, visible state, and the failure is made known instead of being hidden.
<<<

[REQUIREMENT]
UID: STK-004
STATUS: Draft
KIND: Functional
VERIFICATION: Demonstration
TITLE: Diagnose the vehicle without opening it
STATEMENT: >>>
A service engineer, at the vehicle or remotely, can read the status and faults of every vehicle node through standard diagnostic interfaces.
<<<

[REQUIREMENT]
UID: STK-005
STATUS: Draft
KIND: Non-functional
VERIFICATION: Demonstration
TITLE: Evolve functions independently of hardware
STATEMENT: >>>
Engineers can change, test and update vehicle functions without being tied to a specific hardware unit, including running the whole vehicle without hardware.
<<<

[REQUIREMENT]
UID: STK-006
STATUS: Draft
KIND: Functional
VERIFICATION: Demonstration
TITLE: Operate the vehicle like with an ignition key
STATEMENT: >>>
The operator can switch the vehicle off, on and into an update mode, as with an ignition key, and sees the vehicle functions follow that state.
<<<
RATIONALE: >>>
Vehicle functions behave differently depending on the vehicle state, and software updates need a safe state to be applied in (ADR 0006).
<<<

[REQUIREMENT]
UID: STK-007
STATUS: Draft
KIND: Functional
VERIFICATION: Demonstration
RELEVANCE: Security
TITLE: Enter and start the vehicle with a key
STATEMENT: >>>
Only a person with a valid key can unlock the vehicle and switch it on.
<<<
RATIONALE: >>>
Access control is part of every production vehicle; on the bench it is shown by the door / digital-key module (ADR 0008).
<<<

[REQUIREMENT]
UID: STK-008
STATUS: Draft
KIND: Functional
VERIFICATION: Demonstration
TITLE: Know the vehicle status at a glance
STATEMENT: >>>
The driver can see the indicator and hazard status, the vehicle state, update progress and active warnings without a diagnostic tool.
<<<
RATIONALE: >>>
Shown on the bench by the instrument cluster (ADR 0008).
<<<
