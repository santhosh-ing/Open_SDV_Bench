[DOCUMENT]
TITLE: 10 System requirements

[GRAMMAR]
IMPORT_FROM_FILE: bench.sgra

[TEXT]
STATEMENT: >>>
Level 1: what the vehicle as a whole shall do, independent of how it is split into functions and nodes. Verified by system tests on the bench. IDs: SYS-<AREA>-NNN. Each traces to a stakeholder need (STK).
<<<

[[SECTION]]
TITLE: Exterior lighting

[REQUIREMENT]
UID: SYS-LIGHT-001
STATUS: Draft
KIND: Functional
VERIFICATION: Test
MILESTONE: M1
TITLE: Direction indication
STATEMENT: >>>
The vehicle shall provide left and right direction indication on request.
<<<
RELATIONS:
- TYPE: Parent
  VALUE: STK-001

[REQUIREMENT]
UID: SYS-LIGHT-002
STATUS: Draft
KIND: Functional
VERIFICATION: Test
MILESTONE: M1
RELEVANCE: Safety
TITLE: Hazard warning
STATEMENT: >>>
The vehicle shall provide a hazard warning signal on request, which takes priority over direction indication.
<<<
RELATIONS:
- TYPE: Parent
  VALUE: STK-001

[REQUIREMENT]
UID: SYS-LIGHT-003
STATUS: Draft
KIND: Functional
VERIFICATION: Test
TITLE: Comfort blink
STATEMENT: >>>
The vehicle shall provide comfort blink: a short direction request produces a configured number of indication flashes.
<<<
RATIONALE: >>>
Lane-change convenience offered by most production vehicles; the number of flashes is market-specific and therefore configurable (variant coding).
<<<
RELATIONS:
- TYPE: Parent
  VALUE: STK-001

[REQUIREMENT]
UID: SYS-LIGHT-004
STATUS: Draft
KIND: Functional
VERIFICATION: Test
MILESTONE: M1
TITLE: Low beam
STATEMENT: >>>
The vehicle shall switch its low beam on and off on request.
<<<
RELATIONS:
- TYPE: Parent
  VALUE: STK-002

[REQUIREMENT]
UID: SYS-LIGHT-005
STATUS: Draft
KIND: Functional
VERIFICATION: Test
RELEVANCE: Safety
TITLE: Front and rear indication in phase
STATEMENT: >>>
The vehicle shall show direction indication and the hazard warning signal at the front and at the rear, with all active indicator lamps flashing in phase.
<<<
RATIONALE: >>>
Other road users must see the signal from both directions. With the extended topology (ADR 0008) front and rear lamps sit on two zone controllers (ZC-STM32, ZC-S32K).
<<<
COMMENT: >>>
How the two zones stay in phase is open (ADR 0008). It may revise ADR 0005, where indication is local to the ZC-STM32.
<<<
RELATIONS:
- TYPE: Parent
  VALUE: STK-001

[[/SECTION]]

[[SECTION]]
TITLE: Vehicle state

[REQUIREMENT]
UID: SYS-VEH-001
STATUS: Draft
KIND: Functional
VERIFICATION: Test
MILESTONE: M2
TITLE: Vehicle states
STATEMENT: >>>
The vehicle shall have the vehicle states Off, On and Update, set by one central vehicle state manager, and every vehicle node shall follow the current vehicle state.
<<<
RATIONALE: >>>
One master for the vehicle state gives one source of truth (ADR 0006).
<<<
RELATIONS:
- TYPE: Parent
  VALUE: STK-006

[[/SECTION]]

[[SECTION]]
TITLE: Access

[REQUIREMENT]
UID: SYS-ACC-001
STATUS: Draft
KIND: Functional
VERIFICATION: Test
RELEVANCE: Security
TITLE: Unlock with a valid key
STATEMENT: >>>
When a valid key is presented at the door, the vehicle shall unlock the door; when an invalid key is presented, the vehicle shall keep the door locked and record the attempt as a fault event.
<<<
COMMENT: >>>
Response time to be agreed. On the bench a key is an NFC card read by the ZC-Door (ADR 0008). Matching only the card UID is a known demo limitation.
<<<
RELATIONS:
- TYPE: Parent
  VALUE: STK-007

[REQUIREMENT]
UID: SYS-ACC-002
STATUS: Draft
KIND: Functional
VERIFICATION: Test
RELEVANCE: Security
TITLE: Valid key before vehicle On
STATEMENT: >>>
The vehicle shall change its vehicle state from Off to On only after a valid key has been presented.
<<<
RATIONALE: >>>
The key is an input to the central vehicle state manager, not a second mode source (ADR 0006, ADR 0008).
<<<
COMMENT: >>>
Open: how this combines with the dashboard that sets the vehicle state today (ADR 0006).
<<<
RELATIONS:
- TYPE: Parent
  VALUE: STK-006
- TYPE: Parent
  VALUE: STK-007

[[/SECTION]]

[[SECTION]]
TITLE: Driver information

[REQUIREMENT]
UID: SYS-HMI-001
STATUS: Draft
KIND: Functional
VERIFICATION: Test
TITLE: Driver information display
STATEMENT: >>>
The vehicle shall display to the driver the direction indication and hazard status, the current vehicle state and whether faults are active.
<<<
COMMENT: >>>
On the bench this is the instrument cluster (Riverdi display, ADR 0008). Whether the cluster may also set the vehicle state is open.
<<<
RELATIONS:
- TYPE: Parent
  VALUE: STK-008

[REQUIREMENT]
UID: SYS-HMI-002
STATUS: Draft
KIND: Functional
VERIFICATION: Test
TITLE: Update progress display
STATEMENT: >>>
While the vehicle state is Update, the vehicle shall display the progress and the result of the software update to the driver.
<<<
RELATIONS:
- TYPE: Parent
  VALUE: STK-006
- TYPE: Parent
  VALUE: STK-008

[[/SECTION]]

[[SECTION]]
TITLE: Robustness and safe behaviour

[REQUIREMENT]
UID: SYS-SAFE-001
STATUS: Draft
KIND: Functional
VERIFICATION: Test
MILESTONE: M1
RELEVANCE: Safety
TITLE: Defined degraded lighting state
STATEMENT: >>>
If a lighting node loses its commands, the vehicle shall enter a defined degraded lighting state that keeps the vehicle visible, and shall report that it is degraded.
<<<
RELATIONS:
- TYPE: Parent
  VALUE: STK-003

[REQUIREMENT]
UID: SYS-SAFE-002
STATUS: Draft
KIND: Non-functional
VERIFICATION: Analysis
MILESTONE: M1
RELEVANCE: Safety
TITLE: Deterministic node behaviour
STATEMENT: >>>
Every vehicle node shall behave deterministically and repeatably during start-up and normal operation.
<<<
RELATIONS:
- TYPE: Parent
  VALUE: STK-003

[[/SECTION]]

[[SECTION]]
TITLE: Diagnostics

[REQUIREMENT]
UID: SYS-DIAG-001
STATUS: Draft
KIND: Functional
VERIFICATION: Test
MILESTONE: M3
TITLE: Diagnostic access to every node
STATEMENT: >>>
Every vehicle node shall provide its status and detected faults through a diagnostic interface.
<<<
RELATIONS:
- TYPE: Parent
  VALUE: STK-004

[[/SECTION]]

[[SECTION]]
TITLE: Architecture

[REQUIREMENT]
UID: SYS-ARCH-001
STATUS: Draft
KIND: Constraint
VERIFICATION: Inspection
TITLE: Functions decoupled from hardware
STATEMENT: >>>
Vehicle functions shall be decoupled from the hardware they run on, so that a hardware node can be replaced by its virtual twin without changing the functions.
<<<
RELATIONS:
- TYPE: Parent
  VALUE: STK-005

[[/SECTION]]
