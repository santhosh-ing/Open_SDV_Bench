[DOCUMENT]
TITLE: 20 Function requirements

[GRAMMAR]
IMPORT_FROM_FILE: bench.sgra

[TEXT]
STATEMENT: >>>
Level 2: behaviour of the logical functions (see docs/architecture/logical/), still independent of the node a function runs on. Verified by integration tests against the HPC and the virtual twins. IDs: FUN-<AREA>-NNN. Each traces to a system requirement (SYS). Allocation to a node happens one level down.
<<<

[[SECTION]]
TITLE: Indicator and hazard function

[REQUIREMENT]
UID: FUN-LIGHT-001
STATUS: Draft
KIND: Functional
VERIFICATION: Test
MILESTONE: M1
TITLE: Indicator flashing
STATEMENT: >>>
When the left or the right indicator is requested and no hazard is requested, the indicator function shall flash only the requested side at 1.5 Hz with a 50 % duty cycle.
<<<
RELATIONS:
- TYPE: Parent
  VALUE: SYS-LIGHT-001

[REQUIREMENT]
UID: FUN-LIGHT-002
STATUS: Draft
KIND: Functional
VERIFICATION: Test
MILESTONE: M1
RELEVANCE: Safety
TITLE: Hazard priority
STATEMENT: >>>
While the hazard warning is requested, the indicator function shall flash both sides in phase, regardless of any left or right indicator request.
<<<
RELATIONS:
- TYPE: Parent
  VALUE: SYS-LIGHT-002

[REQUIREMENT]
UID: FUN-LIGHT-003
STATUS: Draft
KIND: Functional
VERIFICATION: Test
MILESTONE: M1
TITLE: Invalid indicator combination
STATEMENT: >>>
If the left and the right indicator are requested at the same time without a hazard request, the indicator function shall flash neither side.
<<<
COMMENT: >>>
Open question from spec 002 (to be settled in /speckit-clarify): confirm this behaviour.
<<<
RELATIONS:
- TYPE: Parent
  VALUE: SYS-LIGHT-001

[REQUIREMENT]
UID: FUN-LIGHT-010
STATUS: Draft
KIND: Functional
VERIFICATION: Test
TITLE: Comfort blink
STATEMENT: >>>
When the driver taps a direction request for less than 0.5 s, the indicator function shall flash the selected side the coded number of times (default 3).
<<<
RATIONALE: >>>
Lane-change convenience; the number of flashes is market-specific (variant coding).
<<<
COMMENT: >>>
Allocated to the ZC-STM32: the joystick is connected to the body zone and the indication logic runs there (ADR 0005).
<<<
RELATIONS:
- TYPE: Parent
  VALUE: SYS-LIGHT-003

[REQUIREMENT]
UID: FUN-LIGHT-011
STATUS: Draft
KIND: Functional
VERIFICATION: Test
MILESTONE: M1
TITLE: Indication while held
STATEMENT: >>>
While the driver holds a direction request for 0.5 s or longer, the indicator function shall flash the selected side until the request is released, and shall complete the flash that is in progress.
<<<
RATIONALE: >>>
The joystick springs back to its centre, so it cannot latch like a real stalk. It behaves like the stalk's non-locking "touch" position: a tap gives comfort blink (FUN-LIGHT-010), holding gives continuous indication.
<<<
COMMENT: >>>
Proposed default (2026-11-01). Alternative: latching indication (tap left = on, tap again = off).
<<<
RELATIONS:
- TYPE: Parent
  VALUE: SYS-LIGHT-001

[REQUIREMENT]
UID: FUN-LIGHT-012
STATUS: Draft
KIND: Functional
VERIFICATION: Test
MILESTONE: M1
RELEVANCE: Safety
TITLE: Hazard request sources
STATEMENT: >>>
The hazard warning shall be requested while the driver's local hazard switch is toggled on, or while the central computer requests it.
<<<
RATIONALE: >>>
The local switch keeps hazard available when the central computer cannot be reached (ADR 0006). The central request keeps cross-domain functions possible, e.g. emergency brake to hazard (milestone M5).
<<<
RELATIONS:
- TYPE: Parent
  VALUE: SYS-LIGHT-002

[[/SECTION]]

[[SECTION]]
TITLE: Vehicle state handling

[REQUIREMENT]
UID: FUN-VEH-001
STATUS: Draft
KIND: Functional
VERIFICATION: Test
MILESTONE: M2
RELEVANCE: Safety
TITLE: Lighting follows the vehicle state
STATEMENT: >>>
While the vehicle state is Off or Update, the indicator function shall not flash for direction requests; the hazard warning shall remain available in every vehicle state.
<<<
RATIONALE: >>>
Production-vehicle concept: direction indication needs the vehicle switched on, hazard works even with the vehicle off (ADR 0006).
<<<
COMMENT: >>>
Proposed default for Update (2026-11-01): direction indication off, hazard available.
<<<
RELATIONS:
- TYPE: Parent
  VALUE: SYS-VEH-001
- TYPE: Parent
  VALUE: SYS-LIGHT-002

[[/SECTION]]

[[SECTION]]
TITLE: Low beam function

[REQUIREMENT]
UID: FUN-LIGHT-004
STATUS: Draft
KIND: Functional
VERIFICATION: Test
MILESTONE: M1
TITLE: Low beam switching
STATEMENT: >>>
While low beam is requested, the low beam function shall keep the low beam on; otherwise it shall keep it off.
<<<
RELATIONS:
- TYPE: Parent
  VALUE: SYS-LIGHT-004

[[/SECTION]]

[[SECTION]]
TITLE: Fail-safe and fault reporting

[REQUIREMENT]
UID: FUN-SAFE-001
STATUS: Draft
KIND: Functional
VERIFICATION: Test
MILESTONE: M1
RELEVANCE: Safety
TITLE: Communication-loss fail-safe
STATEMENT: >>>
If no valid light command or no valid vehicle state has been received for 500 ms or longer, the lighting functions shall switch the low beam on, ignore all central requests, keep direction indication and hazard warning from the driver's local inputs available as in vehicle state On, and report a degraded state; when valid messages return, they shall resume normal behaviour automatically.
<<<
RATIONALE: >>>
Low beam on keeps the vehicle visible. Local indication and hazard stay usable because they do not depend on the central computer (ADR 0005, ADR 0006). Hazard is not switched on automatically, as in production vehicles. The 500 ms timeout is five missed 100 ms cycles (ADR 0002, ADR 0007).
<<<
COMMENT: >>>
Changed 2026-11-01: before ADR 0005/0006 the indicators were switched off on command loss.
<<<
RELATIONS:
- TYPE: Parent
  VALUE: SYS-SAFE-001

[REQUIREMENT]
UID: FUN-DIAG-001
STATUS: Draft
KIND: Functional
VERIFICATION: Test
MILESTONE: M1
TITLE: Actual state and fault reporting
STATEMENT: >>>
The lighting functions shall report their actual lamp states, their operating state and detected faults to the rest of the vehicle and to diagnostic access.
<<<
RELATIONS:
- TYPE: Parent
  VALUE: SYS-DIAG-001

[[/SECTION]]
