[DOCUMENT]
TITLE: 30 ZC-STM32 component requirements

[GRAMMAR]
IMPORT_FROM_FILE: bench.sgra

[TEXT]
STATEMENT: >>>
Level 3: requirements allocated to the body zone controller (ZC-STM32, STM32F407G-DISC1). Verified by host unit tests and by tests on the board. IDs: SW-ZCS-NNN (software) and HW-ZCS-NNN (hardware). Each traces to a function requirement (FUN) or, for constraints, to a system requirement (SYS). Spec Kit specs implement these IDs.
<<<

[[SECTION]]
TITLE: CAN communication

[REQUIREMENT]
UID: SW-ZCS-001
STATUS: Draft
KIND: Constraint
ALLOCATED_TO: ZC-STM32
VERIFICATION: Test
MILESTONE: M1
LEGACY_ID: REQ-BODY-002
TITLE: CAN contract conformance
STATEMENT: >>>
The ZC-STM32 shall accept and transmit only the CAN frames defined in the body CAN contract (interfaces/can/body.dbc).
<<<
RATIONALE: >>>
The DBC is the single source of truth for CAN communication; pack/unpack code is generated from it.
<<<
RELATIONS:
- TYPE: Parent
  VALUE: SYS-ARCH-001

[REQUIREMENT]
UID: SW-ZCS-002
STATUS: Draft
KIND: Functional
ALLOCATED_TO: ZC-STM32
VERIFICATION: Test
MILESTONE: M1
RELEVANCE: Safety
TITLE: Light command validation
STATEMENT: >>>
The ZC-STM32 shall use the signals of BODY_LightCmd only after validating its CAN ID, a DLC of 8 and its alive counter.
<<<
RELATIONS:
- TYPE: Parent
  VALUE: FUN-SAFE-001

[REQUIREMENT]
UID: SW-ZCS-003
STATUS: Draft
KIND: Functional
ALLOCATED_TO: ZC-STM32
VERIFICATION: Test
MILESTONE: M1
TITLE: Light status transmission
STATEMENT: >>>
The ZC-STM32 shall transmit BODY_LightStatus every 100 ms ± 10 ms with the actual lamp states, blink phase, command-timeout flag, ECU state and a rolling alive counter.
<<<
RELATIONS:
- TYPE: Parent
  VALUE: FUN-DIAG-001

[[/SECTION]]

[[SECTION]]
TITLE: Light functions

[REQUIREMENT]
UID: SW-ZCS-010
STATUS: Draft
KIND: Functional
ALLOCATED_TO: ZC-STM32
VERIFICATION: Test
MILESTONE: M1
LEGACY_ID: REQ-BODY-001
TITLE: Light outputs and central requests
STATEMENT: >>>
The ZC-STM32 shall control its low beam output according to LowBeamReq and use HazardReq as the central hazard request, both within one 100 ms command cycle; it shall take direction requests only from the local joystick, not from the CAN bus.
<<<
COMMENT: >>>
Changed 2026-11-01 (ADR 0005): IndicatorLeftReq and IndicatorRightReq are no longer used; the contract change is proposed in ADR 0007.
<<<
RELATIONS:
- TYPE: Parent
  VALUE: FUN-LIGHT-004
- TYPE: Parent
  VALUE: FUN-LIGHT-012

[REQUIREMENT]
UID: SW-ZCS-011
STATUS: Draft
KIND: Functional
ALLOCATED_TO: ZC-STM32
VERIFICATION: Test
MILESTONE: M1
TITLE: Blink timing
STATEMENT: >>>
The ZC-STM32 shall blink indicator outputs at 1.5 Hz with a 50 % duty cycle, and left and right outputs blinking at the same time shall be in phase.
<<<
RELATIONS:
- TYPE: Parent
  VALUE: FUN-LIGHT-001
- TYPE: Parent
  VALUE: FUN-LIGHT-002

[[/SECTION]]

[[SECTION]]
TITLE: ECU states and fail-safe

[REQUIREMENT]
UID: SW-ZCS-020
STATUS: Draft
KIND: Functional
ALLOCATED_TO: ZC-STM32
VERIFICATION: Test
MILESTONE: M1
RELEVANCE: Safety
LEGACY_ID: REQ-BODY-003
TITLE: Explicit ECU states
STATEMENT: >>>
The ZC-STM32 shall implement the explicit ECU states Init, Normal, Degraded and Fault with defined transitions, and shall report the current state on the bus.
<<<
RELATIONS:
- TYPE: Parent
  VALUE: FUN-SAFE-001
- TYPE: Parent
  VALUE: FUN-DIAG-001

[REQUIREMENT]
UID: SW-ZCS-021
STATUS: Draft
KIND: Functional
ALLOCATED_TO: ZC-STM32
VERIFICATION: Test
MILESTONE: M1
RELEVANCE: Safety
TITLE: Communication timeout handling
STATEMENT: >>>
If no valid BODY_LightCmd or no valid VEH_State has been received for 500 ms or longer, the ZC-STM32 shall enter state Degraded, switch the low beam output on, ignore HazardReq and LowBeamReq, keep joystick indication and the local hazard switch working as in vehicle state On, and set CmdTimeout or VehStateTimeout accordingly; when both messages are valid again, it shall return to state Normal.
<<<
COMMENT: >>>
Changed 2026-11-01 (ADR 0006): previously the indicator outputs were switched off. VEH_State and VehStateTimeout are proposed in ADR 0007.
<<<
RELATIONS:
- TYPE: Parent
  VALUE: FUN-SAFE-001

[REQUIREMENT]
UID: SW-ZCS-022
STATUS: Draft
KIND: Functional
ALLOCATED_TO: ZC-STM32
VERIFICATION: Demonstration
MILESTONE: M1
TITLE: Heartbeat indication
STATEMENT: >>>
The ZC-STM32 shall blink its heartbeat LED at 1 Hz in state Normal and at 4 Hz in state Degraded.
<<<
RATIONALE: >>>
Makes the ECU state visible on the bench without a debugger.
<<<
RELATIONS:
- TYPE: Parent
  VALUE: FUN-DIAG-001

[REQUIREMENT]
UID: SW-ZCS-023
STATUS: Verified
KIND: Non-functional
ALLOCATED_TO: ZC-STM32
VERIFICATION: Analysis
MILESTONE: M1
RELEVANCE: Safety
LEGACY_ID: REQ-SYS-001
TITLE: Deterministic start-up and operation
STATEMENT: >>>
The ZC-STM32 shall behave deterministically during start-up and normal operation: fixed task periods from a 1 ms time base, no dynamic memory allocation and no blocking waits in application code.
<<<
RELATIONS:
- TYPE: Parent
  VALUE: SYS-SAFE-002

[[/SECTION]]

[[SECTION]]
TITLE: Driver inputs

[REQUIREMENT]
UID: SW-ZCS-050
STATUS: Draft
KIND: Functional
ALLOCATED_TO: ZC-STM32
VERIFICATION: Test
MILESTONE: M1
TITLE: Joystick direction classification
STATEMENT: >>>
The ZC-STM32 shall sample the joystick X axis every 10 ms with 12-bit resolution and classify it as left below 1024, right above 3072 and neutral between 1536 and 2560, keep the previous classification in between (hysteresis), and use a new classification only after it has been stable for 50 ms.
<<<
RATIONALE: >>>
Hysteresis and a stability time prevent flicker around the thresholds and from mechanical bounce.
<<<
COMMENT: >>>
Which end of the axis is "left" depends on how the joystick is mounted: a named constant, checked on the bench. Thresholds are candidates for parameters (OTA demo, later).
<<<
RELATIONS:
- TYPE: Parent
  VALUE: FUN-LIGHT-001
- TYPE: Parent
  VALUE: FUN-LIGHT-010
- TYPE: Parent
  VALUE: FUN-LIGHT-011

[REQUIREMENT]
UID: SW-ZCS-051
STATUS: Draft
KIND: Functional
ALLOCATED_TO: ZC-STM32
VERIFICATION: Test
MILESTONE: M1
TITLE: Tap and hold
STATEMENT: >>>
When a joystick direction returns to neutral less than 500 ms after it was classified, the ZC-STM32 shall flash that side 3 times (comfort blink); while a direction stays classified for 500 ms or longer, it shall flash that side until the joystick returns to neutral.
<<<
COMMENT: >>>
A new direction request cancels a running comfort blink and starts the new one.
<<<
RELATIONS:
- TYPE: Parent
  VALUE: FUN-LIGHT-010
- TYPE: Parent
  VALUE: FUN-LIGHT-011

[REQUIREMENT]
UID: SW-ZCS-052
STATUS: Draft
KIND: Functional
ALLOCATED_TO: ZC-STM32
VERIFICATION: Test
MILESTONE: M1
RELEVANCE: Safety
TITLE: Local hazard switch
STATEMENT: >>>
The ZC-STM32 shall debounce the joystick push button and toggle its local hazard request on each press, in every vehicle state and in state Degraded.
<<<
RATIONALE: >>>
Hazard must be switchable when the central computer is unreachable (ADR 0006).
<<<
RELATIONS:
- TYPE: Parent
  VALUE: FUN-LIGHT-012

[[/SECTION]]

[[SECTION]]
TITLE: Vehicle state

[REQUIREMENT]
UID: SW-ZCS-053
STATUS: Draft
KIND: Functional
ALLOCATED_TO: ZC-STM32
VERIFICATION: Test
MILESTONE: M2
RELEVANCE: Safety
TITLE: Vehicle state reception
STATEMENT: >>>
The ZC-STM32 shall use VEH_State only after validating its CAN ID, a DLC of 8 and its alive counter, and shall apply a valid vehicle state within one 100 ms cycle.
<<<
COMMENT: >>>
VEH_State is proposed in ADR 0007 (body.dbc v0.2.0). Until it is received for the first time after start-up, the ZC-STM32 treats the vehicle state as Off.
<<<
RELATIONS:
- TYPE: Parent
  VALUE: FUN-VEH-001

[REQUIREMENT]
UID: SW-ZCS-054
STATUS: Draft
KIND: Functional
ALLOCATED_TO: ZC-STM32
VERIFICATION: Test
MILESTONE: M2
RELEVANCE: Safety
TITLE: Indication gated by the vehicle state
STATEMENT: >>>
While the vehicle state is Off or Update and the ZC-STM32 is not in state Degraded, it shall ignore joystick direction requests and cancel any running indication, while hazard remains available.
<<<
RELATIONS:
- TYPE: Parent
  VALUE: FUN-VEH-001

[[/SECTION]]

[[SECTION]]
TITLE: Hardware

[REQUIREMENT]
UID: HW-ZCS-001
STATUS: Draft
KIND: Constraint
ALLOCATED_TO: ZC-STM32
VERIFICATION: Inspection
MILESTONE: M1
TITLE: Joystick connection
STATEMENT: >>>
The joystick shall be powered from the 3V supply of the STM32F407G-DISC1, with its X axis on PA1 (ADC1_IN1), its Y axis on PA2 (ADC1_IN2, reserved) and its push button on PE7 with the internal pull-up enabled.
<<<
RATIONALE: >>>
The axis outputs follow the supply, and the ADC inputs accept at most 3.3 V. The pins are not used by on-board peripherals (MB997 schematic). Wiring: docs/hardware/wiring/joystick.yml.
<<<
RELATIONS:
- TYPE: Parent
  VALUE: FUN-LIGHT-011
- TYPE: Parent
  VALUE: FUN-LIGHT-012

[[/SECTION]]

[[SECTION]]
TITLE: Diagnostics

[REQUIREMENT]
UID: SW-ZCS-030
STATUS: Draft
KIND: Functional
ALLOCATED_TO: ZC-STM32
VERIFICATION: Test
MILESTONE: M3
LEGACY_ID: REQ-DIAG-001
TITLE: Diagnostic interface
STATEMENT: >>>
The ZC-STM32 shall provide a UDS diagnostic interface for status and fault reporting as defined in interfaces/diag/body_ecu.yaml.
<<<
RELATIONS:
- TYPE: Parent
  VALUE: FUN-DIAG-001

[[/SECTION]]

[[SECTION]]
TITLE: Software architecture constraints

[REQUIREMENT]
UID: SW-ZCS-040
STATUS: Draft
KIND: Constraint
ALLOCATED_TO: ZC-STM32
VERIFICATION: Inspection
MILESTONE: M1
LEGACY_ID: REQ-SW-001
TITLE: Generated code kept separate
STATEMENT: >>>
The ZC-STM32 software shall keep generated code (STM32CubeMX output, DBC code generation) separate from hand-written application code.
<<<
RATIONALE: >>>
Regenerating code must never overwrite project code.
<<<
RELATIONS:
- TYPE: Parent
  VALUE: SYS-ARCH-001

[REQUIREMENT]
UID: SW-ZCS-041
STATUS: Draft
KIND: Constraint
ALLOCATED_TO: ZC-STM32
VERIFICATION: Inspection
MILESTONE: M1
LEGACY_ID: REQ-SW-002
TITLE: Layered software architecture
STATEMENT: >>>
The ZC-STM32 software shall be structured in the layers functions, com, diag, bsp and sched, where each layer only calls the layers below it and only bsp and com call the hardware abstraction layer.
<<<
RATIONALE: >>>
The same function logic then runs unchanged in the virtual twin and in host unit tests (ADR 0001).
<<<
RELATIONS:
- TYPE: Parent
  VALUE: SYS-ARCH-001

[[/SECTION]]
